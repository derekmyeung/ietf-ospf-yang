module ietf-ospf-bfd {
  namespace "urn:ietf:params:xml:ns:yang:ietf-ospf-bfd";

  prefix ospf-bfd;

  import ietf-routing {
    prefix "rt";
  }
  import ietf-ospf {
    prefix "ospf";
  }

  organization
    "Cisco Systems
     170 West Tasman Drive
     San Jose, CA 95134-1706
     USA";

  contact
     "WG Web:   <http://tools.ietf.org/wg/ospf/>
      WG List:  <mailto:ospf@ietf.org>

      WG Chair: Acee Lindem
                <mailto:acee@cisco.com>

      WG Chair: Abhay Roy
                <mailto:akr@cisco.com>

      Editor:   Derek Yeung
                <mailto:derek@arrcus.com>
      Author:   Derek Yeung
                <mailto:derek@arrcus.com>
      Author:   Yingzhen Qu
                <mailto:yiqu@cisco.com>
      Author:   Acee Lindem
                <mailto:acee@cisco.com>
      Author:   Jeffrey Zhang
                <mailto:zzhang@juniper.net>
      Author:   Ing-Wher Chen
                <mailto:ichen@kuatrotech.com>
      Author:   Greg Hankins
                <mailto:greg.hankins@alcatel-lucent.com>";

  description
    "This YANG module defines the generic configuration
     and operational state for OSPF BFD, which is common
     across all of the vendor implementations. It is
     intended that the module will be extended by vendors to
     define vendor-specific OSPF BFD configuration
     and operational parameters and policies.

     Terms and Acronyms

     OSPF (ospf): Open Shortest Path First

     IP (ip): Internet Protocol

     IPv4 (ipv4):Internet Protocol Version 4

     IPv6 (ipv6): Internet Protocol Version 6
    ";

  revision 2016-10-31 {
    description
      "* Update authors information.
       * Rename bfd/enabled to bfd/enable";
    reference
      "RFC XXXX: A YANG Data Model for OSPF BFD.";
  }

  revision 2016-07-07 {
    description
      "* Change routing-protocol to control-plane-protocol.";
    reference
      "RFC XXXX: A YANG Data Model for OSPF BFD.";
  }

  revision 2016-03-20 {
    description
      "* Remove routing-instance.
       * Remove use of bfd-protocol-parms from ietf-bfd module.
       * Remove import of ietf-bfd module.";
    reference
      "RFC XXXX: A YANG Data Model for OSPF BFD.";
  }

  revision 2015-10-19 {
    description
      "Initial revision.";
    reference
      "RFC XXXX: A YANG Data Model for OSPF BFD.";
  }

  /* Configuration */

  augment "/rt:routing/rt:control-plane-protocols/"
        + "rt:control-plane-protocol/ospf:ospf/ospf:instance/"
        + "ospf:areas/ospf:area/ospf:interfaces/ospf:interface" {
    when "../../../../../../rt:type = 'ospf:ospfv2' or "
       + "../../../../../../rt:type = 'ospf:ospfv3'" {
      description
      "This augments the OSPF routing protocol when used";
    }
    description
     "This augments OSPF protocol configuration
      with BFD.";

    container bfd {
      description "BFD configuration.";
      leaf enable {
        type boolean;
        default false;
        description
          "True if BFD is enabled for the OSPF interface.";
      }
    }
  }

  /* Operational states */

  augment "/rt:routing-state/"
        + "rt:control-plane-protocols/rt:control-plane-protocol/"
        + "ospf:ospf/ospf:instance/ospf:areas/ospf:area/"
        + "ospf:interfaces/ospf:interface" {
    when "../../../../../../rt:type = 'ospf:ospfv2' or "
       + "../../../../../../rt:type = 'ospf:ospfv3'" {
      description
      "This augments the OSPF routing protocol when used";
    }
    description
     "This augments OSPF protocol operation
      with BFD.";

    container bfd {
      description "BFD operation.";
      leaf enable {
        type boolean;
        description
          "True if BFD is enabled for the OSPF interface.";
      }
    }
  }
}
